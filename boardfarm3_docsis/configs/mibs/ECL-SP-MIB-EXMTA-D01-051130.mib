-- ECL: Module name changed to distinguish from CableLabs module
PKTC-ECL-EN-MTA-MIB DEFINITIONS ::= BEGIN

IMPORTS
      MODULE-IDENTITY,
      OBJECT-TYPE
               FROM SNMPv2-SMI
      OBJECT-GROUP,
      MODULE-COMPLIANCE
            FROM SNMPv2-CONF
      pktcEclEnhancements
-- ECL: do not import 'FROM CLAB-DEF-MIB' but 'FROM ECL-DEF-MIB'
            FROM ECL-DEF-MIB;

pktcEclEnMtaMib MODULE-IDENTITY
      LAST-UPDATED    "200501280000Z" -- January 28, 2005
      ORGANIZATION    "Cable Television Laboratories, Inc"

      CONTACT-INFO
            "Sumanth Channabasappa
            Postal: Cable Television Laboratories, Inc.
            858 Coal Creek Circle
            Louisville, Colorado 80027-9750
            U.S.A.
            Phone: +1 303-661-9100
            Fax: +1 303-661-9199
            E-mail: mibs@cablelabs.com"

      DESCRIPTION
            "This MIB module enhances the basic management objects
             defined for the PacketCable MTA Device device by
             the MIB group pktcMtaMib.

            Acknowledgements:
            Rodney Osborne        -      Arris Interactive
            Eugene Nechamkin      -      BroadCom Corporation
            Satish Kumar          -      Texas Instruments
            Jean-Francois Mule    -      CableLabs
            Venkatesh Sunkad      -      CableLabs

            Copyright 1999-2005 Cable Television Laboratories, Inc.
            All rights reserved."

      REVISION        "200501280000Z"
      DESCRIPTION
            "This revision is being published as part of the PacketCable
             MTA MIBs enhancements for PacketCable 1.5."
      ::=  { pktcEclEnhancements 1 }

--
--  PacketCable Enhanced MTA MIB Objects
--
pktcEnMtaMibObjects       OBJECT IDENTIFIER ::= { pktcEclEnMtaMib 1 }
pktcEnMtaDevBase          OBJECT IDENTIFIER ::= { pktcEnMtaMibObjects 1 }
pktcEnMtaDevServer        OBJECT IDENTIFIER ::= { pktcEnMtaMibObjects 2 }
pktcEnMtaDevSecurity      OBJECT IDENTIFIER ::= { pktcEnMtaMibObjects 3 }

--
--  Enhanced notification group.
--
pktcEnMtaNotificationPrefix OBJECT IDENTIFIER ::= { pktcEclEnMtaMib 2 }
pktcEnMtaNotification OBJECT IDENTIFIER       ::= { pktcEnMtaNotificationPrefix 0 }
pktcEnMtaConformance  OBJECT IDENTIFIER       ::= { pktcEclEnMtaMib 3 }
pktcEnMtaCompliances  OBJECT IDENTIFIER       ::= { pktcEnMtaConformance 1 }
pktcEnMtaGroups       OBJECT IDENTIFIER       ::= { pktcEnMtaConformance 2 }

--
--  Enhancement MIB Objects
--
pktcEnMtaDevMltplGrantsPerInterval     OBJECT-TYPE
      SYNTAX INTEGER {
             enablemgpifunctionality(1),
             disablemgpifunctionality(2)
      }
      MAX-ACCESS  read-only
      STATUS      current
      DESCRIPTION
            " This object is used to control the Multiple grants functionality
              on a PacketCable MTA.
              To indicate enabling of this functionality, a value of
              enablemgpifunctionality(1) is used.
              To indicate disabling of this functionality, a value of
              disablemgpifunctionality(2) is used."
      DEFVAL  {disablemgpifunctionality}
      ::= { pktcEnMtaDevBase 1}

--
--  Compliance statements
--
pktcEnMtaBasicCompliance MODULE-COMPLIANCE
      STATUS     current
      DESCRIPTION
            "The compliance statement for devices that implement
            MTA feature."
      MODULE   --PKTC-ECL-EN-MTA-MIB

--
--  Mandatory groups
--
      MANDATORY-GROUPS {
              pktcEnMtaGroup
          }
      ::= { pktcEnMtaCompliances 3 }

pktcEnMtaGroup OBJECT-GROUP
      OBJECTS {
        pktcEnMtaDevMltplGrantsPerInterval
      }
      STATUS    current
      DESCRIPTION
            "Group of Enhanced objects for the PacketCable MTA MIB."
      ::= { pktcEnMtaGroups 1 }
END
